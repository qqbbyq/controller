module globalrpc {
    yang-version 1;
    namespace "urn:opendaylight:params:xml:ns:yang:globalrpc";
    prefix "globalrpc";

    revision "2015-01-05" {
        description "Initial revision of globalrpc model";
    }
}
